[DOCUMENT]
TITLE: Starlark for .NET - futures extension
VERSION: 0.2
OPTIONS:
  ENABLE_MID: True

[GRAMMAR]
ELEMENTS:
- TAG: REQUIREMENT
  FIELDS:
  - TITLE: UID
    TYPE: String
    REQUIRED: True
  - TITLE: STATUS
    TYPE: SingleChoice(Draft, Active, Implemented, Open)
    REQUIRED: True
  - TITLE: TITLE
    TYPE: String
    REQUIRED: True
  - TITLE: STATEMENT
    TYPE: String
    REQUIRED: True
  - TITLE: VERIFICATION
    TYPE: String
    REQUIRED: False
  - TITLE: COMMENT
    TYPE: String
    REQUIRED: False

[FREETEXT]
An opt-in extension that lets a script run work concurrently and collect the results. It is not part of the Starlark
specification and is off unless the host enables the dialect flag. Standard programs behave identically with the flag
off. Revision 0.2 incorporates the findings of a four-way concurrency review (see docs/futures-design.md).
[/FREETEXT]

[SECTION]
TITLE: Prerequisites

[REQUIREMENT]
UID: FUT-PRE-001
STATUS: Implemented
TITLE: Per-call execution context
STATEMENT: >>>
The interpreter shall keep all per-run mutable state (step counter, deadline, call depth, active-recursion set, string
element mode, memory budget, cancellation token, output buffer) in an execution context passed explicitly to each call
and to each task, and shall hold no such state in thread-static or Interpreter fields, so that a frozen module can be
called from many threads at once.
<<<
VERIFICATION: FrozenModuleConcurrencyTests (many threads call one frozen module; the execution context holds all per-run state)

[REQUIREMENT]
UID: FUT-PRE-002
STATUS: Implemented
TITLE: Thread-safe frozen modules
STATEMENT: >>>
Calling functions of a frozen module concurrently from many threads shall give the same results as calling them one at
a time, shown by a stress test that includes shared frozen lists, dicts and sets iterated concurrently.
<<<
VERIFICATION: FrozenModuleConcurrencyTests.ManyThreadsCallTheSameFunction, SharedFrozenCollectionsAreIteratedConcurrently

[REQUIREMENT]
UID: FUT-PRE-003
STATUS: Implemented
TITLE: Frozen values are not written
STATEMENT: >>>
Iterating a frozen list, dict or set shall not write to it. No operation on a frozen value shall write any field of it.
<<<
VERIFICATION: FrozenModuleConcurrencyTests.SharedFrozenCollectionsAreIteratedConcurrently

[REQUIREMENT]
UID: FUT-PRE-004
STATUS: Implemented
TITLE: No load or Execute inside a task
STATEMENT: >>>
load() and Interpreter.Execute shall not run inside a task. The module cache shall only be touched at module top level.
<<<
VERIFICATION: FuturesReview2Tests.ExecuteInsideATaskIsRefused

[/SECTION]

[SECTION]
TITLE: Language

[REQUIREMENT]
UID: FUT-LANG-001
STATUS: Implemented
TITLE: Dialect flags
STATEMENT: >>>
The names parallel_map, spawn and all_of and the future type shall exist only when the dialect flag EnableFutures is
set. The names done and first_of shall exist only when the further flag EnableNondeterministicFutures is also set. With
the flags off the names shall not resolve.
<<<
VERIFICATION: FuturesTests.NamesAreAbsentWithoutTheFlag; FuturesReview2Tests.DialectNamesFollowTheFlags

[REQUIREMENT]
UID: FUT-LANG-002
STATUS: Implemented
TITLE: parallel_map
STATEMENT: >>>
parallel_map(function, iterable) shall call function on each element, possibly on other threads, and return the
results as a list in iteration order.
<<<
VERIFICATION: FuturesTests.ParallelMapKeepsInputOrder; FuturesProperties.ParallelMapEqualsInline

[REQUIREMENT]
UID: FUT-LANG-003
STATUS: Implemented
TITLE: spawn and get
STATEMENT: >>>
spawn(function, *args, **kwargs) shall start the call and return a future immediately. future.get() shall block until
the call finishes and return its result, or raise the error the call raised with its original source location, as a
fresh exception on every call.
<<<
VERIFICATION: FuturesTests.SpawnAndGet, GetRaisesTheTasksError

[REQUIREMENT]
UID: FUT-LANG-004
STATUS: Implemented
TITLE: all_of
STATEMENT: >>>
all_of(futures) shall wait for every future and return the results as a list in argument order. If any call failed it
shall raise the error of the lowest-index failed future after all have finished.
<<<
VERIFICATION: FuturesTests.AllOfKeepsArgumentOrder, AllOfReportsTheLowestIndexFailure

[REQUIREMENT]
UID: FUT-LANG-005
STATUS: Implemented
TITLE: Callable restriction
STATEMENT: >>>
The function passed to parallel_map or spawn shall be a builtin, a host function, or a top-level function of a loaded,
frozen module. A function that captures variables of a live frame shall be rejected with an error that says so.
<<<
VERIFICATION: FuturesTests.ClosuresOverLiveFramesAreRejected; FuturesReview2Tests.ClosureThroughAGlobalIsRejectedNotMisBound

[REQUIREMENT]
UID: FUT-LANG-006
STATUS: Implemented
TITLE: Isolation by copying
STATEMENT: >>>
Mutable arguments shall be deep-copied for the task, preserving aliasing among the arguments, and the caller's values
shall not be frozen or otherwise changed. The task shall see a frozen snapshot of exactly the module-level values its
function references. The result shall be frozen. No frame, binding or non-frozen value shall be shared between a task
and any other thread.
<<<
VERIFICATION: FuturesTests.SpawnDoesNotFreezeTheCallersValues, TasksMutateTheirOwnCopy, ResultsAreFrozen

[REQUIREMENT]
UID: FUT-LANG-007
STATUS: Implemented
TITLE: Determinism
STATEMENT: >>>
The observable result of a program (return values, errors, printed output order and the step count charged) shall not
depend on thread scheduling, except for deadline expiry and the nondeterministic profile (FUT-LANG-011).
<<<
VERIFICATION: FuturesAbuseTests.ResultsDoNotDependOnScheduling, ErrorsDoNotDependOnScheduling; FuturesProperties

[REQUIREMENT]
UID: FUT-LANG-008
STATUS: Implemented
TITLE: Futures do not escape
STATEMENT: >>>
A future shall not be hashable, shall have no truth value, shall not be stored in a module global, shall not be
returned from the function that created it, and shall not be passed to spawn or parallel_map. A future still pending
when the spawning call or module ends shall be an error.
<<<
VERIFICATION: FuturesTests.FuturesCannotBeStoredAsGlobals; FuturesReview2Tests.FuturesCannotBeReturnedFromTheirFunction

[REQUIREMENT]
UID: FUT-LANG-009
STATUS: Implemented
TITLE: Task restrictions
STATEMENT: >>>
A task shall not call spawn, parallel_map, get or all_of, so the task graph has depth 1.
<<<
VERIFICATION: FuturesTests.TasksCannotSpawnOrCollect; FuturesAbuseTests.ForkBombStopsAtDepthOne

[REQUIREMENT]
UID: FUT-LANG-010
STATUS: Implemented
TITLE: Recursion across tasks
STATEMENT: >>>
A task shall inherit the active-call set and depth of its spawner, so spawning a function that is already on the call
stack is a recursion error.
<<<
VERIFICATION: FuturesTests.SpawningAFunctionOnTheStackIsRecursion

[REQUIREMENT]
UID: FUT-LANG-011
STATUS: Implemented
TITLE: Nondeterministic profile
STATEMENT: >>>
Under EnableNondeterministicFutures, future.done() shall return whether the call has finished without blocking, and
first_of(futures) shall return the index and result of the first to finish. Both shall be documented as
nondeterministic and shall charge steps.
<<<
VERIFICATION: NondeterministicFuturesTests (5 run, 3 skipped)
COMMENT: Three tests that leave a held worker alive past teardown are skipped: they intermittently abort the test host and the cause is not yet explained.

[REQUIREMENT]
UID: FUT-LANG-012
STATUS: Implemented
TITLE: Output order
STATEMENT: >>>
Output printed by a task shall be buffered and emitted when the task is joined, in index order.
<<<
VERIFICATION: FuturesTests.TaskOutputIsOrdered; FuturesProperties.OutputOrderMatchesInline

[/SECTION]

[SECTION]
TITLE: Host integration

[REQUIREMENT]
UID: FUT-HOST-001
STATUS: Implemented
TITLE: Host tasks as futures by registration
STATEMENT: >>>
A registered host function that returns Task shall return a future to the script only if registered with the AsFuture
option. Otherwise it shall keep blocking the script thread as it does today.
<<<
VERIFICATION: HostFuturesTests.AsFutureOperationsOverlap, WithoutAsFutureTheCallWaits

[REQUIREMENT]
UID: FUT-HOST-002
STATUS: Implemented
TITLE: Shared deadline, token and slices
STATEMENT: >>>
All tasks of a run shall share the run's absolute deadline and a cancellation token linked to the run token. Each task
shall receive a deterministic slice of the remaining step budget and shall be charged against the run's memory budget,
and the parent shall be charged the steps actually used when the task is joined. A host function called from a task
shall receive that task's token.
<<<
VERIFICATION: FuturesTests.StepLimitAppliesInsideTasks, TimeoutStopsATask, CancellationStopsTasks; FuturesReviewRegressionTests

[REQUIREMENT]
UID: FUT-HOST-003
STATUS: Implemented
TITLE: Concurrency cap that cannot deadlock
STATEMENT: >>>
The host shall be able to cap the number of tasks running at once for a run (default 4). The cap shall never block the
spawning script, and tasks shall run on a dedicated bounded scheduler, not on the shared thread pool.
<<<
VERIFICATION: FuturesAbuseTests.MoreTasksThanWorkersFinish, ScriptTasksDoNotUseTheSharedThreadPool

[REQUIREMENT]
UID: FUT-HOST-004
STATUS: Implemented
TITLE: Spawn and future caps
STATEMENT: >>>
The host shall be able to cap total spawns per run (default 10,000) and live uncollected futures (default 1,000).
Exceeding a cap shall raise ExecutionLimitException with Limit "tasks" or "futures". Each spawn shall charge steps
(default 1,000).
<<<
VERIFICATION: FuturesTests.TotalSpawnsAreCapped, LiveFuturesAreCapped, SpawningCostsSteps

[REQUIREMENT]
UID: FUT-HOST-005
STATUS: Implemented
TITLE: Limit errors are never lost
STATEMENT: >>>
An ExecutionLimitException or cancellation in any task shall cancel the other tasks and fail the run with that
exception, whether or not the script collected the future, and shall never be converted into a StarlarkException.
<<<
VERIFICATION: FuturesTests.LimitsInTasksAreNotScriptErrors; FuturesAbuseTests.OneHostileTaskEndsTheWholeRun

[REQUIREMENT]
UID: FUT-HOST-006
STATUS: Implemented
TITLE: Teardown
STATEMENT: >>>
When a run ends (normally, by error, by cancellation or by disposal) the run shall stop accepting spawns, cancel its
tasks, wait for them for a bounded grace period (default 5 s), observe every fault, and report tasks that did not stop.
No UnobservedTaskException shall result.
<<<
VERIFICATION: FuturesAbuseTests.WorkersAreReleasedAfterEachRun, FailingRunsTearDownToo, NoUnobservedTaskExceptions; FuturesReviewRegressionTests.LateWorkersAfterTeardownDoNotCrash

[REQUIREMENT]
UID: FUT-HOST-007
STATUS: Implemented
TITLE: Host operation caps
STATEMENT: >>>
The host shall be able to cap in-flight host operations started from tasks (default 8). Each Task-returning host call
shall charge steps (default 100).
<<<
VERIFICATION: HostFuturesTests.InFlightOperationsAreCapped, SlotsAreReleasedWhenOperationsFinish, HostCallsCostSteps

[REQUIREMENT]
UID: FUT-HOST-008
STATUS: Implemented
TITLE: Thread-safety of host code
STATEMENT: >>>
Host values handed to a task shall be frozen or declared thread-safe, and the universe shall be frozen when futures are
enabled. A host function shall be called concurrently only if registered as thread-safe; otherwise calls shall be
serialised per run with deadline-aware waiting.
<<<
VERIFICATION: FuturesReview2Tests.HostValuesMustBeThreadSafe, UniverseValuesAreFrozenWhenTasksRun, HostCallsFromTasksAreSerialisedByDefault

[REQUIREMENT]
UID: FUT-HOST-009
STATUS: Implemented
TITLE: Run statistics
STATEMENT: >>>
Every run shall expose its counts of steps, spawns, peak live futures, peak concurrency, host calls and leaked tasks to
the host.
<<<
VERIFICATION: HostFuturesTests.StatisticsIncludeHostCallsAndSteps; FuturesTests.StatsAreReported

[/SECTION]

[SECTION]
TITLE: Verification

[REQUIREMENT]
UID: FUT-VER-001
STATUS: Implemented
TITLE: Equivalence property
STATEMENT: >>>
A property test shall show that, for generated programs, parallel_map and spawn/get give the same values, errors and
printed output as calling the function inline, under randomized scheduling delays.
<<<
VERIFICATION: FuturesProperties (six property tests; a planted ordering bug was caught within 10 cases)

[REQUIREMENT]
UID: FUT-VER-002
STATUS: Implemented
TITLE: Checker support
STATEMENT: >>>
When the flag is set the static checker shall know the future type and type parallel_map as Callable[[T], U],
Iterable[T] to list[U], and spawn, get and all_of with their result types.
<<<
VERIFICATION: FuturesCheckerTests; HostFuturesTests.CheckerKnowsTheReturnType
COMMENT: Provided as signatures for parallel_map, spawn and all_of plus a future type name. A parametrized future[T] annotation is not provided.

[REQUIREMENT]
UID: FUT-VER-003
STATUS: Implemented
TITLE: Review regressions
STATEMENT: >>>
Tests shall cover: a loop-captured lambda rejected or deterministic; a spawn that does not freeze the caller's locals;
a spawn at module top level followed by more definitions; Utf8 mode and the memory limit inside tasks; the same function
from many tasks; a fork bomb; a million-future list; a cap-saturation case; a host function that ignores its token; and
a run under a single-thread synchronization context.
<<<
VERIFICATION: FuturesReviewRegressionTests, FuturesReview2Tests, FuturesAbuseTests


[REQUIREMENT]
UID: FUT-HOST-010
STATUS: Implemented
TITLE: Platforms without threads
STATEMENT: >>>
On a platform that cannot start threads (browser WebAssembly, WASI), tasks shall run inline on the spawning thread, and a
program shall give the same results, errors and printed output as with worker threads. A host shall be able to choose
inline mode on any platform.
<<<
VERIFICATION: InlineFuturesTests (every futures example program run both ways); the playground self test in a browser

[/SECTION]
