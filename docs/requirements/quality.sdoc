[DOCUMENT]
TITLE: Starlark for .NET - quality, tooling and delivery
VERSION: 0.1
OPTIONS:
  ENABLE_MID: True

[GRAMMAR]
ELEMENTS:
- TAG: REQUIREMENT
  FIELDS:
  - TITLE: UID
    TYPE: String
    REQUIRED: True
  - TITLE: STATUS
    TYPE: SingleChoice(Draft, Active, Implemented, Open)
    REQUIRED: True
  - TITLE: TITLE
    TYPE: String
    REQUIRED: True
  - TITLE: STATEMENT
    TYPE: String
    REQUIRED: True
  - TITLE: VERIFICATION
    TYPE: String
    REQUIRED: False
  - TITLE: COMMENT
    TYPE: String
    REQUIRED: False

[FREETEXT]
How the project is tested, measured, documented and shipped.
[/FREETEXT]

[SECTION]
TITLE: Testing

[REQUIREMENT]
UID: QA-TST-001
STATUS: Implemented
TITLE: Unit and conformance tests
STATEMENT: >>>
The repository shall contain xunit tests for the syntax and evaluation layers and the official conformance data, and
all shall pass.
<<<
VERIFICATION: dotnet test

[REQUIREMENT]
UID: QA-TST-002
STATUS: Implemented
TITLE: Example programs as tests
STATEMENT: >>>
There shall be at least 50 example Starlark programs that state their expected output or error in comments and are
executed by one parameterized test.
<<<
VERIFICATION: ExampleProgramTests.ThereAreFiftyOrMoreExamples

[REQUIREMENT]
UID: QA-TST-008
STATUS: Implemented
TITLE: Sample applications as tests
STATEMENT: >>>
Each sample application (Adventure, BuildRules, ConfigInspector, GameAI, Mandelbrot, ParallelBuilds, PolicyEngine, RayTracer,
ReportPipeline) shall be run by a test that asserts on its key output, and the Level II BASIC interpreter written in
Starlark shall be tested for its statements, DATA/READ, the EDIT command, non-ASCII text and the SIN demonstration program.
<<<
VERIFICATION: AppTests, ExamplesTests, BasicTests, BasicExprTests, BasicDataTests, BasicEditTests, BasicNonAsciiTests, BasicSineTests

[REQUIREMENT]
UID: QA-TST-003
STATUS: Implemented
TITLE: Fuzzing
STATEMENT: >>>
Seeded fuzzers shall exercise the lexer, parser, interpreter and checker, with iteration count and seed settable by
environment variable.
<<<
VERIFICATION: Starlark.Fuzz.Tests

[REQUIREMENT]
UID: QA-TST-004
STATUS: Implemented
TITLE: Property tests
STATEMENT: >>>
Hedgehog property tests with shrinking shall check invariants of the parser, interpreter and checker.
<<<
VERIFICATION: Starlark.Fuzz.Tests (PropertyTests)

[REQUIREMENT]
UID: QA-TST-005
STATUS: Implemented
TITLE: FsCheck properties
STATEMENT: >>>
FsCheck properties shall complement the Hedgehog ones for the value model and the host interop conversions.
<<<
VERIFICATION: Starlark.Fuzz.Tests (InteropProperties)

[REQUIREMENT]
UID: QA-TST-006
STATUS: Active
TITLE: Mutation testing
STATEMENT: >>>
Stryker.NET shall run against Starlark.Eval and Starlark.Syntax with the configuration in stryker-config.json, and the
build shall fail below the break threshold.
<<<
VERIFICATION: stryker-config.json; tools/MutantReport; OpsMutationTests, MethodsMutationTests
COMMENT: Ops.cs went 73.5% to 93.7% and Methods.cs 79.2% to 84.8% after adding survivor tests. Values, StringFormat, Json, Interpreter, the checker, Ty and Interop are not yet run.

[REQUIREMENT]
UID: QA-ROB-001
STATUS: Active
TITLE: No crash on any input
STATEMENT: >>>
No input shall make the lexer, parser, checker, interpreter or host interface crash, hang, or consume unbounded memory or
disk. Malformed, truncated, hostile and oversized input shall end in a bounded, reported error. Every component that reads
user input shall have error-path and truncation tests, an exhaustive test over all short strings of a small alphabet where
the input has a grammar, and a guard that fails fast if a loop over input stops making progress.
<<<
VERIFICATION: LexerRegressionTests (exhaustive short inputs, progress guard); ExhaustiveInputTests; StackDepthTests; ReleaseCandidate1Tests (review findings: cyclic and deep host conversion, int size cap, bounded strings, futures limits) (deep and cyclic values); BoundedExpansionTests; NestingLimitTests (Go's 1000-level nesting limit on every parser path, the parser call-graph check, 200,000 nested ifs); GoLimitsTests (the deepest allowed program on a 1 MB stack, long operator chains, Go's repetition and shift limits, a big script stack and 100,000-deep recursion); AuditInteropTests (endless host sequences stopped by the run's limits in direct and asFuture calls, host failures as script errors in every mode, Expose rejecting overloads and uncallable methods); Starlark.Fuzz.Tests (DeepNestingNeverCrashes); tools/Soak with child memory cap and disk floor; AuditSyntaxTests (linear f-string format specs, bounded error snippets, escaped invalid-input text); AuditAppTests (BASIC ON..GOSUB limit, huge line numbers, long-line expression cache, Basic, ConfigInspector, CommentCheck and Serve command-line errors); AuditRegressionTests (deep runtime types and load chains on a 1 MB thread, the checker linear and under the run's timeout, shared tuples and huge iterations stopped by the limits, concatenation, list growth, formatting and json.indent within the memory budget, host failures in Define and print as script errors)
COMMENT: Added after an unterminated f-string format spec (f'{:) made the lexer loop and exhaust memory during a soak run. Extended on 2026-11-06 after deeply nested source text (1000 nested lists, unary operators or `not`, or a 1000-term sum) crashed the process with a stack overflow; the limits adopted from Starlark-Go are listed in docs/DEVIATIONS.md.

[REQUIREMENT]
UID: QA-TST-007
STATUS: Active
TITLE: Fourteen-hour soak
STATEMENT: >>>
A C# soak tool shall run the fuzzers and property tests in a loop for a configurable duration (default 14 hours), with
a fresh seed per round, a wall-clock limit per input, failing inputs written to disk, periodic progress and memory
logging, and the ability to resume.
<<<
VERIFICATION: tools/Soak; a first 5-hour run found 116 failing rounds and 6 hangs, all fixed (BoundedExpansionTests)
COMMENT: Part A of an 18-hour run (three 6-hour parts with a fix pass between) is queued; mark Implemented when the run completes clean.

[/SECTION]

[SECTION]
TITLE: Coverage

[REQUIREMENT]
UID: QA-COV-001
STATUS: Implemented
TITLE: Coverage report
STATEMENT: >>>
A C# tool shall merge Cobertura reports from all test projects and write Markdown and HTML summaries with per-file
uncovered lines.
<<<
VERIFICATION: tools/CoverageReport

[REQUIREMENT]
UID: QA-COV-002
STATUS: Open
TITLE: Coverage targets
STATEMENT: >>>
Total line coverage shall be at least 96 percent, and Methods.cs, Values.cs and StringFormat.cs at least 95 percent each.
<<<
COMMENT: Currently 94.4 percent lines and 88.1 percent branches.

[/SECTION]

[SECTION]
TITLE: Performance

[REQUIREMENT]
UID: QA-PERF-001
STATUS: Implemented
TITLE: Own benchmark
STATEMENT: >>>
A benchmark project shall measure lexer, parser and interpreter throughput.
<<<
VERIFICATION: bench/Starlark.Bench

[REQUIREMENT]
UID: QA-PERF-002
STATUS: Open
TITLE: Comparison with the Rust implementation
STATEMENT: >>>
Lexer and parser speed shall be compared with starlark-rust on the same inputs and the result recorded.
<<<
COMMENT: Needs a Rust toolchain, which is not installed.

[/SECTION]

[SECTION]
TITLE: Documentation and packaging

[REQUIREMENT]
UID: QA-DOC-001
STATUS: Implemented
TITLE: Deviations
STATEMENT: >>>
Deliberate deviations from the specification and from the reference implementations, and the embedding limits, shall
be recorded in docs/DEVIATIONS.md.
<<<
VERIFICATION: docs/DEVIATIONS.md

[REQUIREMENT]
UID: QA-DOC-002
STATUS: Implemented
TITLE: Embedding guide and example applications
STATEMENT: >>>
There shall be an embedding guide and runnable example applications that show host functions, object exposure, loading,
limits, type checking and error reporting, with automated tests.
<<<
VERIFICATION: ManualTests (every code sample in docs/MANUAL.md and README.md is run), AppTests
COMMENT: The guide is docs/MANUAL.md; docs/site/deep-dive.html explains the implementation with live examples, checked in a headless browser by tools/BuildSite --check.

[REQUIREMENT]
UID: QA-DOC-003
STATUS: Implemented
TITLE: Requirements traceability
STATEMENT: >>>
Every Implemented requirement shall name a verifying test, and a check shall fail the build when a named test does not
exist.
<<<
VERIFICATION: tools/Trace (exit code 1 when an Implemented requirement names no existing test)
COMMENT: Trace is a tool run by hand, not yet part of a build: wiring it into CI belongs to QA-PKG-002.

[REQUIREMENT]
UID: QA-PKG-001
STATUS: Open
TITLE: NuGet packages
STATEMENT: >>>
Starlark.Syntax and Starlark.Eval shall build as NuGet packages with metadata, XML documentation and a README.
<<<

[REQUIREMENT]
UID: QA-PKG-002
STATUS: Open
TITLE: Continuous integration
STATEMENT: >>>
A CI workflow shall build, test with coverage, enforce the coverage threshold and run mutation tests on a schedule.
<<<

[/SECTION]

[SECTION]
TITLE: Project conventions

[REQUIREMENT]
UID: QA-CON-001
STATUS: Active
TITLE: Language and tooling
STATEMENT: >>>
Helper programs shall be written in C#. Requirements shall be kept in StrictDoc. Code comments shall be XML
documentation comments. Property testing shall use Hedgehog and FsCheck, and mutation testing Stryker.NET.
<<<
COMMENT: The test runner stays xunit by the owner's decision.

[/SECTION]
